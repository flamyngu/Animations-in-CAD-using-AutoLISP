;; Simulates vl-sleep for nanoCAD 5
;; milliseconds: delay time in milliseconds (1000 = 1 second)
(defun my-sleep (milliseconds / start-time end-time current-time)
  (setq start-time (getvar "DATE"))
  (setq end-time (+ start-time (/ milliseconds 86400000.0))) ; Convert ms to days (AutoCAD DATE format)
  (while (< (getvar "DATE") end-time)
    ; Busy wait loop - keeps checking current time
    (setq current-time (getvar "DATE"))
  )
)

;; Legacy pause function that uses my-sleep
;; seconds: delay time in seconds (can be fractional, e.g., 0.5 for half second)
(defun pause (seconds)
  (if (not seconds) (setq seconds 1))
  (my-sleep (* seconds 1000))
)

(defun str-trim (str / start end)
  ;; Trim leading and trailing spaces from a string
  (setq start 1)
  (while (and (<= start (strlen str))
              (= (substr str start 1) " "))
    (setq start (1+ start))
  )
  (setq end (strlen str))
  (while (and (>= end start)
              (= (substr str end 1) " "))
    (setq end (1- end))
  )
  (if (> end (1- start))
    (substr str start (- end start -1))
    ""
  )
)

(defun str-split (str delim / pos result part len delim-len)
  ;; Split a string by a delimiter and return a list of parts
  (setq delim-len (strlen delim))
  (setq result '())
  (setq len (strlen str))
  (setq pos 1)
  (while (<= pos len)
    (setq part "")
    (while (and (<= pos len) (not (= (substr str pos delim-len) delim)))
      (setq part (strcat part (substr str pos 1)))
      (setq pos (1+ pos))
    )
    (setq result (append result (list part)))
    (setq pos (+ pos delim-len))
  )
  result
)

(defun parse-pbm-line (line / trimmed split nums)
  (setq trimmed (str-trim line))
  (setq split (str-split trimmed " "))
  ;; Convert split strings to integers
  (setq nums '())
  (foreach s split
    (if (not (equal s ""))
      (setq nums (append nums (list (atoi s))))
    )
  )
  nums
)

(defun draw-rect-horizontal-line (row start-col end-col scale / y x1 x2)
  (setq y (* (- row) scale))
  (setq x1 (* start-col scale))
  (setq x2 (+ (* (1+ end-col) scale) 0))
  (entmake
    (list
      '(0 . "LWPOLYLINE")
      '(100 . "AcDbEntity")
      '(100 . "AcDbPolyline")
      '(90 . 4) 
      '(70 . 1) 
      (cons 10 (list x1 y))
      (cons 10 (list x2 y))
      (cons 10 (list x2 (- y scale)))
      (cons 10 (list x1 (- y scale)))
    )
  )
)


(defun draw-horizontal-line (row start-col end-col scale / p1 p2 y x1 x2)
  (setq y (* (- row) scale))
  (setq x1 (* start-col scale))
  (setq x2 (+ (* (1+ end-col) scale) 0))
  (setq p1 (list x1 y 0))
  (setq p2 (list x2 y 0))
  (command "_.LINE" p1 p2 "")
)

(defun draw-line-segments-in-row (row data scale / col start in-segment)
  (setq col 0
        in-segment nil)
  (while (< col (length data))
    (if (= (nth col data) 1)
      (if (not in-segment)
        (progn
          (setq in-segment t)
          (setq start col)
        )
      )
      (if in-segment
        (progn
          (draw-rect-horizontal-line row start (1- col) scale)
          (setq in-segment nil)
        )
      )
    )
    (setq col (1+ col))
  )
  (if in-segment
    (draw-rect-horizontal-line row start (1- col) scale)
  )
)

(defun draw-frame (filename / file line row data scale)
  (setq scale 20) ;; Default scale factor

  (setq file (open filename "r"))
  ;; Read PBM header
  (read-line file)
  (read-line file)

  (setq row 0)
  (while (setq line (read-line file))
    (if (and (> (strlen (str-trim line)) 0)
             (/= (substr line 1 1) "#"))
      (progn
        (setq data (parse-pbm-line line))
        (draw-line-segments-in-row row data scale)
        (setq row (1+ row))
      )
    )
  )
  (close file)
  (princ "\nFertig gezeichnet.")
)

(defun c:drawpbm ()
  (princ "\nBefehl drawpbm gestartet")
  (setq filename (getfiled "PBM-Datei wählen" "" "pbm" 0))
  (if filename
    (draw-frame filename)
    (princ "\nKeine Datei gewählt.")
  )
  (princ)
)

(defun c:testcmd ()
  (princ "\nTestbefehl ausgeführt.")
  (command "RECTANGLE" "0,0" "5,5")
  (princ)
)

(defun load-frames-list-from-txt (filepath / frames f line)
  (setq frames '())
  (setq f (open filepath "r"))
  (if (not f)
    (progn (princ (strcat "\nDatei nicht gefunden: " filepath)) nil)
    (progn
      (while (setq line (read-line f))
        (if (/= line "") 
          (setq frames (append frames (list line)))
        )
      )
      (close f)
      frames
    )
  )
)

(defun play-frames-from-list (frames / i frame-count start-time)
  (if (not frames)
    (princ "\nKeine Frames zum Abspielen vorhanden.")
    (progn
      ;; Setup - Switch to Model Space and set initial zoom
      (command "_.MSPACE")
      (setq frame-count (length frames))
      (princ (strcat "\nStarte Animation mit " (itoa frame-count) " Frames..."))
      
      ;; Set zoom once at the beginning for better performance
      (command "_.ZOOM" "_WINDOW" "-13048,-8490" "22623,8733")
      (princ "\nZoom auf Animationsbereich gesetzt.")
      
      ;; Turn off unnecessary redraws for better performance
      (setvar "REGENMODE" 0)
      
      ;; Animation loop
      (setq i 0
            start-time (getvar "DATE"))
      (while (< i frame-count)
        
        ;; Clear previous frame (skip for first frame)
        (if (> i 0)
          (progn
            (command "_.ERASE" "_ALL" "")
          )
        )
        
        ;; Draw current frame
        (princ (strcat "\rFrame: " (itoa (1+ i)) "/" (itoa frame-count)))
        (draw-frame (nth i frames))
        
        ;; Force redraw for immediate visual update
        (command "_.REDRAW")
        
        ;; Short pause for animation timing
        (pause 0.05)
        
        (setq i (1+ i))
      )
      
      ;; Cleanup and final status
      (setvar "REGENMODE" 1)
      (setq end-time (getvar "DATE"))
      (princ (strcat "\n\nAnimation abgeschlossen! " 
                     (itoa frame-count) " Frames in " 
                     (rtos (* (- end-time start-time) 86400) 2 2) " Sekunden."))
    )
  )
  (princ)
)

(defun c:PBMPLAY (/ filepath frames)
  (princ "\nBitte Textdatei mit Frame-Pfaden auswählen:")
  (setq filepath (getfiled "Textdatei mit Frame-Pfaden wählen" "" "txt" 0))
  (if (not filepath)
    (princ "\nKeine Datei ausgewählt. Abbruch.")
    (progn
      (setq frames (load-frames-list-from-txt filepath))
      (play-frames-from-list frames)
    )
  )
  (princ)
)
